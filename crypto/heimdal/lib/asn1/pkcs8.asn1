-- $Id: pkcs8.asn1,v 1.1.1.1 2012-07-21 15:09:08 laffer1 Exp $ --

PKCS8 DEFINITIONS ::=

BEGIN

IMPORTS	Attribute, AlgorithmIdentifier FROM rfc2459
	heim_any, heim_any_set FROM heim;

PKCS8PrivateKeyAlgorithmIdentifier ::= AlgorithmIdentifier

PKCS8PrivateKey ::= OCTET STRING

PKCS8Attributes ::= SET OF Attribute

PKCS8PrivateKeyInfo ::= SEQUENCE {
  version INTEGER,
  privateKeyAlgorithm PKCS8PrivateKeyAlgorithmIdentifier,
  privateKey PKCS8PrivateKey,
  attributes [0] IMPLICIT SET OF Attribute OPTIONAL
}

PKCS8EncryptedData ::= OCTET STRING

PKCS8EncryptedPrivateKeyInfo ::= SEQUENCE {
    encryptionAlgorithm AlgorithmIdentifier,
    encryptedData PKCS8EncryptedData 
}

END
